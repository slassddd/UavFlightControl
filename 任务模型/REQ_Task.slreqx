# REQ_Task

## #1: 事件数据存储 (Container)

## #2: 异常保护逻辑 (Container)

### #3: 大风保护 (Functional)
当风速大于13.8m/s持续0.2s以上时，触发大风返航机制。

### #4: 低电量返航 (Functional)

#### #5: 电池低电量返航 (Functional)
电池电量低于TaskParam.low_battery_alarm_set或由飞行性能模块触发动态电量返航时，飞机进入返航模式。

#### #6: 低电量返航后的暂停模式返航保护 (Functional)
当触发低电量返航后，若人为使飞机进入暂停模式（AirStandby或Hoveradjust），则将周期性触发返航，避免人为疏忽造成飞机长期处于暂停模式而消耗过多电量无法安全返航。

#### #7: 电池极低电量立即降落 (Functional)
电池电量低于TaskParam.severe_low_battery_alarm_set ，且飞机没有处于返航过程，则触发立即降落。

#### #8: 旋翼动态低电量立即降落 (Functional)
旋翼模式下，当飞行性能模块触发立即降落，且飞机处于非AutoProfile流程，且飞机异常切换旋翼或当前离地高度大于阈值，则触发立即降落

#### #9: 低电量着陆后的暂停模式降落保护 (Functional)
当触发低电量降落后，若人为使飞机进入暂停模式Hoveradjust，则将周期性触发降落，避免人为疏忽造成飞机长期处于暂停模式而消耗过多电量无法安全着陆。
